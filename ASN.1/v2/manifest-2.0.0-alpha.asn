-- -*- coding: utf-8 -*-
-- ----------------------------------------------------------------------------
-- Copyright 2017 ARM Limited or its affiliates
--
-- SPDX-License-Identifier: Apache-2.0
--
-- Licensed under the Apache License, Version 2.0 (the "License");
-- you may not use this file except in compliance with the License.
-- You may obtain a copy of the License at
--
--     http://www.apache.org/licenses/LICENSE-2.0
--
-- Unless required by applicable law or agreed to in writing, software
-- distributed under the License is distributed on an "AS IS" BASIS,
-- WITHOUT WARRANTIES OR CONDITIONS OF ANY KIND, either express or implied.
-- See the License for the specific language governing permissions and
-- limitations under the License.
-- ----------------------------------------------------------------------------
-- Manifest definition file in ASN.1 (v. 2.0.0-alpha)
ManifestSchema DEFINITIONS IMPLICIT TAGS ::= BEGIN

Uri ::= UTF8String
Bytes ::= OCTET STRING
UUID ::= OCTET STRING
Payload ::= OCTET STRING

AlgorithmIdentifier ::= SEQUENCE  {
     algorithm               OBJECT IDENTIFIER,
     parameters              ANY DEFINED BY algorithm OPTIONAL  }

KeyId ::= OCTET STRING

KdfParameters ::= SEQUENCE {
    kdfAlgorithm AlgorithmIdentifier,
    kdfNonce     OCTET STRING,
    keyId        KeyId
}

WrappedKey ::= SEQUENCE {
           deviceSubjectKeyIdentifier OCTET STRING,
           key                        OCTET STRING
}

KeyTable ::= SEQUENCE {
    keyWrapAlgorithm     AlgorithmIdentifier,
    keySize              INTEGER,
    payloadKeyDigest     OCTET STRING,
    subjectKeyIdentifier OCTET STRING,
    table CHOICE {
       uri               UTF8String,
       integrated        SEQUENCE OF WrappedKey
    }
}

EncryptionInfo ::= SEQUENCE {
    mode ENUMERATED {
        none(0), preSharedKey(1), preSharedKeyKdf(2), keyTable(3)
    },
    config ANY DEFINED BY mode,
    encryptedPayloadHash OCTET STRING
}

PayloadInfo ::= SEQUENCE {
    format      CHOICE {
        enum    ENUMERATED {
            rawBinary(1), hexLocationLengthData(2), elf(3), bsdiff(4)
        },
        objectId    OBJECT IDENTIFIER
    },
    encryptionInfo EncryptionInfo OPTIONAL,
    storageIdentifier OCTET STRING,
    size INTEGER,
    payload CHOICE {
        reference    ResourceReference,
        integrated   OCTET STRING
    }
}

ResourceReference ::= SEQUENCE {
    hash        OCTET STRING,
    uri         Uri
}

ConditionValue ::= CHOICE {
    int INTEGER,
    raw OCTET STRING
}
Condition ::= SEQUENCE {
    type ENUMERATED {
        vendorId(1),
        classId(2),
        deviceId(3),
        lastApplicationTime(4),

        vendorSpecificMinimum(2147483648)
    },
    value ConditionValue
}
DirectiveRule ::= CHOICE {
    int INTEGER,
    bool BOOLEAN,
    raw OCTET STRING
}
Directive ::= SEQUENCE {
    type ENUMERATED {
        applyImmediately(1),
        applyAfter(2),
        restartComponent(3),
        restartSystem(4),
        installationHandler(5),

        vendorSpecificMinimum(2147483648)
    },
    rule DirectiveRule
}

TextField ::= SEQUENCE {
    type ENUMERATED {
        description(0), version(1), vendor(2), model(3)
    },
    value UTF8String
}

Manifest ::= SEQUENCE {
    manifestVersion ENUMERATED {
        v2(2)
    },
    text            SEQUENCE OF TextField OPTIONAL,
    nonce           OCTET STRING,
    digestAlgorithm AlgorithmIdentifier,
    timestamp       INTEGER,
    conditions      SEQUENCE OF Condition,
    directives      SEQUENCE OF Directive,
    aliases         SEQUENCE OF ResourceReference,
    dependencies    SEQUENCE OF ResourceReference,
    payloadInfo     PayloadInfo OPTIONAL
}

END
