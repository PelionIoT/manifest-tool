-- ----------------------------------------------------------------------------
-- Copyright 2019-2021 Pelion
--
-- SPDX-License-Identifier: Apache-2.0
--
-- Licensed under the Apache License, Version 2.0 (the "License");
-- you may not use this file except in compliance with the License.
-- You may obtain a copy of the License at
--
--     http://www.apache.org/licenses/LICENSE-2.0
--
-- Unless required by applicable law or agreed to in writing, software
-- distributed under the License is distributed on an "AS IS" BASIS,
-- WITHOUT WARRANTIES OR CONDITIONS OF ANY KIND, either express or implied.
-- See the License for the specific language governing permissions and
-- limitations under the License.
-- ----------------------------------------------------------------------------

-- Manifest definition file in ASN.1 (v. 1.1.1)
ManifestSchema DEFINITIONS IMPLICIT TAGS ::= BEGIN

  -- Metadata for payload reconstruction
  PayloadMetadata ::= SEQUENCE {
    -- represents reconstructed payload size
    installed-size INTEGER,
    -- represents reconstructed payload digest
    installed-digest OCTET STRING,

    -- Used with 'arm-patch-stream',
    -- never for other payload formats
    precursor-digest OCTET STRING OPTIONAL
  }

  Manifest ::= SEQUENCE {

    -- identifier fields
    vendor-id OCTET STRING,
    class-id OCTET STRING,

    -- update priority to be passed to an application callback
    update-priority INTEGER,

    -- component name
    component-name UTF8String,

    -- payload description --
    payload-version UTF8String,
    payload-digest OCTET STRING,
    payload-size INTEGER,
    payload-uri UTF8String,
    payload-format ENUMERATED {
      -- xx01-xxFF describe payload-format
      -- 01xx-FFxx describe encrypted-format
      raw-binary(1),
      arm-patch-stream(5),
      combined(6),
      encrypted-raw(257),  -- 0x0101
      encrypted-combined(262) -- 0x0106
    },

    -- raw ECDSA signature (r||s) over installed payload
    installed-signature OCTET STRING,

    -- Used with 'arm-patch-stream', 'encrypted-raw'
    -- never for 'raw-binary'
    payload-metadata PayloadMetadata OPTIONAL,

    -- custom data to be passed to an endpoint device
    vendor-data OCTET STRING OPTIONAL
  }

  SignedResource ::= SEQUENCE {
    manifest-version ENUMERATED {
      v3(3)
    },
    manifest Manifest,

    -- raw ECDSA signature (r||s) over Manifest
    signature OCTET STRING
  }

END

-- Encryption Key Schema:
--   the key used to encrypt the payload
--   added by service after SignedResource
-- (Comment out to be ignore by manifest-tool)
-- EncryptionKeySchema DEFINITIONS IMPLICIT TAGS ::= BEGIN
--   EncryptionKey ::= CHOICE {
--     aes-128-bit [1] IMPLICIT OCTET STRING (SIZE(16))
--   }
-- END
