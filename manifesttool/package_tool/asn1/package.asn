-- ----------------------------------------------------------------------------
-- Copyright 2021 Pelion
--
-- SPDX-License-Identifier: Apache-2.0
--
-- Licensed under the Apache License, Version 2.0 (the "License");
-- you may not use this file except in compliance with the License.
-- You may obtain a copy of the License at
--
--     http://www.apache.org/licenses/LICENSE-2.0
--
-- Unless required by applicable law or agreed to in writing, software
-- distributed under the License is distributed on an "AS IS" BASIS,
-- WITHOUT WARRANTIES OR CONDITIONS OF ANY KIND, either express or implied.
-- See the License for the specific language governing permissions and
-- limitations under the License.
-- ----------------------------------------------------------------------------

--Package definition file in ASN.1 --
DescriptorSchema DEFINITIONS IMPLICIT TAGS ::= BEGIN

  String ::= UTF8String
  Int ::= INTEGER
  Bytes ::= OCTET STRING

  -- Image descriptor 
  ImgDescriptor ::= SEQUENCE
  {
     -- Image identifier , also the file name in Linux
     id         String,
     -- Vendor data
     vendor-data Bytes,
     -- Vendor data
     vendor-data-size Int,
     -- Image size
     image-size  Int
  }

  Descriptor ::= SEQUENCE 
  {
     num-of-images INTEGER (0..255),
     descriptors-array SEQUENCE OF ImgDescriptor
  }

END
