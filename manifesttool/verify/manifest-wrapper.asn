-- -*- coding: utf-8 -*-
-- ----------------------------------------------------------------------------
-- Copyright 2017 ARM Limited or its affiliates
--
-- SPDX-License-Identifier: Apache-2.0
--
-- Licensed under the Apache License, Version 2.0 (the "License");
-- you may not use this file except in compliance with the License.
-- You may obtain a copy of the License at
--
--     http://www.apache.org/licenses/LICENSE-2.0
--
-- Unless required by applicable law or agreed to in writing, software
-- distributed under the License is distributed on an "AS IS" BASIS,
-- WITHOUT WARRANTIES OR CONDITIONS OF ANY KIND, either express or implied.
-- See the License for the specific language governing permissions and
-- limitations under the License.
-- ----------------------------------------------------------------------------
-- Manifest wrapper definition file in ASN.1 (v. 1.0.0)

ManifestSchema DEFINITIONS IMPLICIT TAGS ::= BEGIN

  Uri ::= UTF8String
  Bytes ::= OCTET STRING
  UUID ::= OCTET STRING
  Payload ::= OCTET STRING

  CertificateReference ::= SEQUENCE {
      fingerprint  Bytes,
      uri          Uri
  }
  SignatureBlock ::= SEQUENCE {
      signature   OCTET STRING,
      certificates SEQUENCE OF CertificateReference
  }
  ResourceSignature ::= SEQUENCE {
      hash        OCTET STRING,
      signatures SEQUENCE OF SignatureBlock
  }

  SignedResource ::= SEQUENCE {
      resource  ANY,
      signature ResourceSignature
  }

END
