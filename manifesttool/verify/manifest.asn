-- -*- coding: utf-8 -*-
-- ----------------------------------------------------------------------------
-- Copyright 2017 ARM Limited or its affiliates
--
-- SPDX-License-Identifier: Apache-2.0
--
-- Licensed under the Apache License, Version 2.0 (the "License");
-- you may not use this file except in compliance with the License.
-- You may obtain a copy of the License at
--
--     http://www.apache.org/licenses/LICENSE-2.0
--
-- Unless required by applicable law or agreed to in writing, software
-- distributed under the License is distributed on an "AS IS" BASIS,
-- WITHOUT WARRANTIES OR CONDITIONS OF ANY KIND, either express or implied.
-- See the License for the specific language governing permissions and
-- limitations under the License.
-- ----------------------------------------------------------------------------
-- Manifest definition file in ASN.1 (v. 1.0.0)
ManifestSchema DEFINITIONS IMPLICIT TAGS ::= BEGIN

  UUID ::= OCTET STRING
  Manifest ::= SEQUENCE {
      manifestVersion     ENUMERATED {
        v1(1)
      },
      description UTF8String OPTIONAL,
      timestamp   INTEGER,
      vendorId    UUID,
      classId     UUID,
      deviceId    UUID,
      nonce       OCTET STRING,
      vendorInfo      OCTET STRING,
      applyPeriod SEQUENCE {
          validFrom     INTEGER,
          validTo       INTEGER
      } OPTIONAL,
      applyImmediately    BOOLEAN,
      encryptionMode  CHOICE {
          enum    ENUMERATED {
              invalid(0),
              aes-128-ctr-ecc-secp256r1-sha256(1),
              none-ecc-secp256r1-sha256(2),
              none-none-sha256(3)
          },
          objectId    OBJECT IDENTIFIER
      },
      aliases         ANY,
      dependencies    ANY,
      payload         ANY OPTIONAL
  }
END
